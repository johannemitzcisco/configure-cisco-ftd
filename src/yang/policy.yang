module policy {

  namespace "http://example.com/policy";
  prefix policy;

  import ietf-inet-types { prefix inet; }
  import tailf-common { prefix tailf; }
  import tailf-ncs { prefix ncs; }
  import tailf-ned-cisco-fmc { prefix cisco-fmc; }

  description
    "Bla bla...";

  revision 2020-04-23 {
    description
      "Initial revision.";
  }
  
  container service-templates {
    list ftd {
      config "false";
      key name;
      leaf name {
        type string;
      }
      list variable {
        key name;
        leaf name {
          type string;
        }
      }
    } 
  }
  
  grouping action-grouping {
    leaf logBegin {
      type boolean;
      default "false";
    }
    leaf logEnd {
      type boolean;
      default "false";
    }
    leaf sendEventsToFMC {
      type boolean;
      default "false";
    }
    leaf action {
      type enumeration {
        enum "BLOCK";
        enum "ALLOW";
      }
      default "BLOCK";
    }
  }

  list policy-service {
      key service-name;
      uses ncs:service-data;
      ncs:servicepoint configure-cisco-fmc-servicepoint;

      leaf service-name {
        type string;
      }
      list devices {
        key device;
        leaf device {
          type leafref {
            path "/ncs:devices/ncs:device/ncs:name";
          }
          must "deref(.)/../ncs:capability/ncs:uri='http://tail-f.com/ned/cisco-fmc'
                or deref(.)/../ncs:capability/ncs:uri='http://tail-f.com/ned/cisco-ftd'
                or deref(.)/../ncs:capability/ncs:uri='http://cisco.com/ned/asa'";
      }
      list policy {
        key name;
        uses policy-grouping;
      }
    }
  }
    
    grouping policy-grouping {
      leaf name {
        type string;
      }
      leaf description {
        type string;
      }
      leaf type {
        type enumeration {
          enum "access";
          enum "nat";
        }
        default "access";
      }
      container defaultAction {
        when "../type = 'access'";
        uses action-grouping;
      }

      list rule {
        key name;
        leaf name {
          type string;
        }
        leaf index {
          type uint32;
        }
        uses action-grouping {
          when "../type = 'access'";
        }
        leaf-list source-zone {
          when "../../type = 'access'";
//          type string;
          type leafref {
            path "deref(../../../policy:device)/../ncs:config/cisco-fmc:object/cisco-fmc:securityzones/cisco-fmc:name";
          }
        }
        leaf-list destination-zone {
          when "../../type = 'access'";
          type string;
        }
        leaf type {
          when "../../type = 'nat'";
          type enumeration {
            enum "auto";
            enum "before-manual";
	    enum "after-manual";
          }
        }
        leaf nat-type {
          when "../../type = 'nat'";
          type enumeration {
            enum "STATIC";
            enum "DYNAMIC";
          }
        }
        leaf interfaceIpv6 {
          when "../../type = 'nat'";
          type boolean;
          default "false";
        }
        leaf fallThrough {
          when "../../type = 'nat'";
          type boolean;
          default "false";
        }
        leaf dns {
          when "../../type = 'nat'";
          type boolean;
          default "false";
        }
        leaf routeLookup {
          when "../../type = 'nat'";
          type boolean;
          default "false";
        }
        leaf noProxyArp {
          when "../../type = 'nat'";
          type boolean;
          default "false";
        }
        leaf netToNet {
          when "../../type = 'nat'";
          type boolean;
          default "false";
        }
        leaf sourceInterface {
          type string;
          when "../../type = 'nat'";
        }
        leaf destinationInterface {
          type string;
          when "../../type = 'nat'";
        }
        container source {
          when "../../type = 'nat'  and (../type = 'before-manual' or ../type = 'after-manual')";
          leaf originalSource {
//            type string;
            type leafref {
              path "deref(../../../../policy:device)/../ncs:config/cisco-fmc:object/cisco-fmc:networks/cisco-fmc:name";
            }
          }
          leaf translatedSource {
//            type string;
            type leafref {
              path "deref(../../../../policy:device)/../ncs:config/cisco-fmc:object/cisco-fmc:networks/cisco-fmc:name";
            }
          }
          leaf interfaceIn {
            type boolean;
            default "false";
          }
        }
        leaf unidirectional {
          when "../../type = 'nat' 
               and (../type = 'before-manual' 
                    or ../type = 'after-manual')";
          type boolean;
          default "false";
        }
        leaf interfaceInOriginalDestination {
          when "../../type = 'nat' 
               and (../type = 'before-manual' 
                    or ../type = 'after-manual')";
          type boolean;
          default "false";
        }
        leaf enabled {
          when "../../type = 'nat' 
               and (../type = 'before-manual' 
                    or ../type = 'after-manual')";
          type boolean;
          default "true";
        }
        leaf interfaceInTranslatedNetwork {
          when "../../type = 'nat' 
               and ../type = 'auto'"; 
          type boolean;
          default "false";
        }
        leaf originalNetwork {
//          type string;
          type leafref {
            path "deref(../../../policy:device)/../ncs:config/cisco-fmc:object/cisco-fmc:networks/cisco-fmc:name";
          }
          when "../../type = 'nat' 
               and ../type = 'auto'"; 
        }
        leaf translatedNetwork {
//          type string;
          type leafref {
            path "deref(../../../policy:device)/../ncs:config/cisco-fmc:object/cisco-fmc:networks/cisco-fmc:name";
          }
          when "../../type = 'nat' 
               and ../type = 'auto'"; 
        }
      } 
    }

    list template {
      key name;
      leaf name {
        type leafref {
          path "/ncs:devices/ncs:template/ncs:name";
        }
      }
      list variable {
        key name;
        leaf name {
          type string;
          tailf:non-strict-leafref {
            path "/service-templates/ftd/name";
          }
        }
        leaf value {
          type string;
        }
      }
    }
  
}
